# -*- coding: utf-8 -*-
import sys
import os.path

# Change this by your own FreeCAD lib path to import FreeCAD
if not sys.path.__contains__("/usr/lib/freecad/lib"): 
    sys.path.append("/usr/lib/freecad/lib")

try:
    import SlopedPlanes
except:
    param = FreeCAD.ParamGet('User parameter:Plugins/SlopedPlanesMacro')
    m_current_path = param.GetString('destination','')

    if not m_current_path:
        m_current_path = os.path.realpath(__file__)
        m_current_path = os.path.dirname(m_current_path)

    if not sys.path.__contains__(str(m_current_path)):
        sys.path.append(str(m_current_path))

    try:
        import SlopedPlanes
    except:
        from PySide import QtGui
        folderDialog = QtGui.QFileDialog.getExistingDirectory(None,QtGui.QApplication.translate("SlopedPlanesMacro", "Location of your SlopedPlanesMacro folder", None, QtGui.QApplication.UnicodeUTF8))
        param.SetString('destination',folderDialog)
        m_current_path = param.GetString('destination')
        sys.path.append(str(m_current_path))

        import SlopedPlanes

selection = FreeCADGui.Selection.getSelectionEx()

for select in selection:

    obj = select.Object

    if obj.TypeId == "Sketcher::SketchObject":
        SlopedPlanes.makeSlopedPlanes(obj)
    elif hasattr(obj, 'Proxy'):
        if obj.Proxy.Type == 'Wire':
            SlopedPlanes.makeSlopedPlanes(obj)
